--
-- SORIA-TRAP-MIB.txt
--
-- 1.3.6.1.4.1.3204.31.10

SORIA-TRAP-MIB  DEFINITIONS ::= BEGIN

IMPORTS
      MODULE-IDENTITY,
      OBJECT-TYPE,
      Integer32, IpAddress
            FROM SNMPv2-SMI

      DateAndTime,      DisplayString
            FROM SNMPv2-TC

      soria
            FROM SORIA-SMI
            
      NOTIFICATION-TYPE
            FROM SNMPv2-SMI;

Trap MODULE-IDENTITY
       LAST-UPDATED "201605030000Z"
       ORGANIZATION "NURI Telecom Co., Ltd."
       CONTACT-INFO "Lee Sung-Yeung
                     Postal: NURI-Building
                     BANGBAE-DONG, SEOCHO-GU SEOUL, KOREA
                     E-mail : locap001@nuritelecom.com"
	   DESCRIPTION
	           "(SORIA-project)MIBs for Trap, One-way Notifications (MT ---> (HES) CS)"
	 
-- revision history
	 REVISION         "201605030000Z"
	 DESCRIPTION	   "Delete All NOTIFICATION-TYPE object's Max-ACCESS clause"
	 REVISION         "201604270000Z"
	 DESCRIPTION	   "Change Meter Notification items (kaifa reponse-RFP)"
	 REVISION         "201604260000Z"
	 DESCRIPTION	   "Modified all identifier' first letter: start with lowercase letter(RFC 2578)"
	 REVISION         "201604010000Z"
     DESCRIPTION       "First draft"          
      
            
-- 1.3.6.1.4.1.3204.31.10      
      ::= { soria 10 }
      

-------------------------------------------------------------------------
--  .1.3.6.1.4.1.3204.31.10.1      
trapFromMeter 	 OBJECT IDENTIFIER ::= { Trap 1 }
--  .1.3.6.1.4.1.3204.31.10.2
trapFromMT		 OBJECT IDENTIFIER ::= { Trap 2 }      
  
-----------------------------------------------------------------
-- .1.3.6.1.4.1.3204.31.10.3
trapMeterSerial OBJECT-TYPE
            SYNTAX                  OCTET STRING (SIZE (0..20))
            MAX-ACCESS       		accessible-for-notify
            STATUS                  current
            DESCRIPTION       
                        "Meter Serial (SORIA)"
            ::= { Trap 3 }
-----------------------------------------------------------------




----------------1. Standard events---------------------------------------------------------
--  .1.3.6.1.4.1.3204.31.10.1.1      
changeClock NOTIFICATION-TYPE
	OBJECTS     {trapMeterSerial}
    STATUS      current
    DESCRIPTION
        "Change of clock notification."
::= { trapFromMeter 1 }      

--  .1.3.6.1.4.1.3204.31.10.1.2      
changeParameter NOTIFICATION-TYPE
	OBJECTS     {trapMeterSerial}
    STATUS      current
    DESCRIPTION
        "Change of parameters configuration notification"
::= { trapFromMeter 2 }    

--  .1.3.6.1.4.1.3204.31.10.1.3
selfDiagnosticError NOTIFICATION-TYPE
	OBJECTS     {trapMeterSerial}
    STATUS      current
    DESCRIPTION
        "Self-diagnostic error notification"
::= { trapFromMeter 3 }    
-----------------------------------------------------------------

-------------2. Control logs----------------------------------------------------
--  .1.3.6.1.4.1.3204.31.10.1.4
openBreakerPowerLimitation NOTIFICATION-TYPE
	OBJECTS     {trapMeterSerial}
    STATUS      current
    DESCRIPTION
        "Open breaker due to power limitation notification"
::= { trapFromMeter 4 }

--  .1.3.6.1.4.1.3204.31.10.1.5
openBreakerControl NOTIFICATION-TYPE
	OBJECTS     {trapMeterSerial}
    STATUS      current
    DESCRIPTION
        "Open breaker due to control commands notification"
::= { trapFromMeter 5 }    

--  .1.3.6.1.4.1.3204.31.10.1.6
closeBreakerButton NOTIFICATION-TYPE
	OBJECTS     {trapMeterSerial}
    STATUS      current
    DESCRIPTION
        "Close breaker via press button notification"
::= { trapFromMeter 6 }    


--  .1.3.6.1.4.1.3204.31.10.1.7  
closeBreakerControl NOTIFICATION-TYPE
	OBJECTS     {trapMeterSerial}
    STATUS      current
    DESCRIPTION
        "Close breaker via control commands notification"
::= { trapFromMeter 7}    
-----------------------------------------------------------------

---------------3. Power failure logs for single-phase/poly-phase--------------------------------------------------
longPowerInterruption NOTIFICATION-TYPE
	OBJECTS     {trapMeterSerial}
    STATUS      current
    DESCRIPTION
        "Long power interruption notification"
::= {trapFromMeter 8}   

shortPowerInterruption NOTIFICATION-TYPE
	OBJECTS     {trapMeterSerial}
    STATUS      current
    DESCRIPTION
        "Short power interruption notification"
::= {trapFromMeter 9}  
-----------------------------------------------------------------

-------------------4. Power Quality logs----------------------------------------------
longAbnormalVoltage NOTIFICATION-TYPE
	OBJECTS     {trapMeterSerial}
    STATUS      current
    DESCRIPTION
        "Long-term Under/Over voltage notification"
::= {trapFromMeter 10}  

shortAbnormalVoltage NOTIFICATION-TYPE
	OBJECTS     {trapMeterSerial}
    STATUS      current
    DESCRIPTION
        "Short-term Under/Over voltage notification"
::= {trapFromMeter 11}  

voltageSag NOTIFICATION-TYPE
	OBJECTS     {trapMeterSerial}
    STATUS      current
    DESCRIPTION
        "Voltage sag/swell notification"
::= {trapFromMeter 12}

thd NOTIFICATION-TYPE
	OBJECTS     {trapMeterSerial}
    STATUS      current
    DESCRIPTION
        "THD (time stamp, code of event) notification"
::= {trapFromMeter 13}
-----------------------------------------------------------------


-------------------5. Tampering logs----------------------------------------------
groundFault NOTIFICATION-TYPE
	OBJECTS     {trapMeterSerial}
    STATUS      current
    DESCRIPTION
        "Ground faults notification"
::= {trapFromMeter 14} 

magneticDisturbance NOTIFICATION-TYPE
	OBJECTS     {trapMeterSerial}
    STATUS      current
    DESCRIPTION
        "Magnetic field disturbance  notification"
::= {trapFromMeter 15} 

openFaceCover NOTIFICATION-TYPE
	OBJECTS     {trapMeterSerial}
    STATUS      current
    DESCRIPTION
        "Open face cover notification"
::= {trapFromMeter 16} 

openTerminalCover NOTIFICATION-TYPE
	OBJECTS     {trapMeterSerial}
    STATUS      current
    DESCRIPTION
        "Open terminal cover notification"
::= {trapFromMeter 17}

accessWrongKey NOTIFICATION-TYPE
	OBJECTS     {trapMeterSerial}
    STATUS      current
    DESCRIPTION
        "Access with wrong key notification"
::= {trapFromMeter 18}
-----------------------------------------------------------------

-------------------6. Firmware upgrade logs----------------------------------------------
firmwareReception NOTIFICATION-TYPE
	OBJECTS     {trapMeterSerial}
    STATUS      current
    DESCRIPTION
        "Firmware reception key notification"
::= {trapFromMeter 19}

firmwareVerificationFails NOTIFICATION-TYPE
	OBJECTS     {trapMeterSerial}
    STATUS      current
    DESCRIPTION
        "Firmware verification fails notification"
::= {trapFromMeter 20}

firmwareVerificationOK NOTIFICATION-TYPE
	OBJECTS     {trapMeterSerial}
    STATUS      current
    DESCRIPTION
        "Firmware verification ok notification"
::= {trapFromMeter 21}

firmwareActivationFail NOTIFICATION-TYPE
	OBJECTS     {trapMeterSerial}
    STATUS      current
    DESCRIPTION
        "Firmware activation fails notification"
::= {trapFromMeter 22}

firmwareActivationOK NOTIFICATION-TYPE
	OBJECTS     {trapMeterSerial}
    STATUS      current
    DESCRIPTION
        "Firmware activation ok notification"
::= {trapFromMeter 23}
-----------------------------------------------------------------


-----------------------------------------------------------------    
--  .1.3.6.1.4.1.3204.31.10.2.1
resetFactorySetting NOTIFICATION-TYPE
    STATUS      current
    DESCRIPTION
        "Meter Terminal notification."
::= { trapFromMT 1 }      
      
--  .1.3.6.1.4.1.3204.31.10.2.2     
oTAdownload NOTIFICATION-TYPE
    STATUS      current
    DESCRIPTION
        "Meter Terminal notification."
::= { trapFromMT 2 }

--  .1.3.6.1.4.1.3204.31.10.2.3
timeSync NOTIFICATION-TYPE
    STATUS      current
    DESCRIPTION
        "Meter Terminal notification."
::= { trapFromMT 3 }

--  .1.3.6.1.4.1.3204.31.10.2.4
mTfwUpload NOTIFICATION-TYPE
    STATUS      current
    DESCRIPTION
        "Meter Terminal' F/W Upload notification."
::= { trapFromMT 4 } 
-----------------------------------------------------------------    
     
     
     
 
END
