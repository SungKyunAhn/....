--
-- SORIA-SMI.txt --------------------------------------------------------------------------
--
-- 1.3.6.1.4.1.3204



SORIA-SMI DEFINITIONS ::= BEGIN

IMPORTS
            MODULE-IDENTITY,
            enterprises
                        FROM SNMPv2-SMI;

NuriTelecom MODULE-IDENTITY
            LAST-UPDATED "201603140000Z"
            ORGANIZATION "NURI Telecom Co., Ltd."
            CONTACT-INFO "Lee Sung-Yeung
                          Postal: NURI-Building
                          BANGBAE-BON-DONG, SEOCHO-GU SEOUL, KOREA
                          E-mail : locap001@nuritelecom.com"
            DESCRIPTION
                        "The Structure and identification of Management Information for the
                        NURI-TELECOM  & SORIA enterprise."


			 REVISION         "201603160000Z"
		     DESCRIPTION       "First draft" 


-- Assigned by IANA (http://www.iana.org)
            ::= { enterprises 3204 }


--
-- NURITELECOM system Group --
--
-- 1.3.6.1.4.1.3204.31
soria       OBJECT IDENTIFIER       ::= { NuriTelecom 31}


END
